(command "._erase" (ssget "A") "")
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(78 111 114 109 97 108))) (setvar (vl-list->string '(67 69 76 87 69 73 71 72 84)) 211)(command "._line" '(1.58 10.0) '(2.08 10.0) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 10.0) 0.04 0 (vl-list->string '(78 111 114 109 97 108)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 101 103 100 32 48))) (setvar (vl-list->string '(67 69 76 87 69 73 71 72 84)) 211)(command "._line" '(1.58 9.9) '(2.08 9.9) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.9) 0.04 0 (vl-list->string '(48 48 70 65 48 48 32 101 103 100 32 48)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 101 103 68 32 49))) (setvar (vl-list->string '(67 69 76 87 69 73 71 72 84)) 211)(command "._line" '(1.58 9.8) '(2.08 9.8) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.8) 0.04 0 (vl-list->string '(48 48 70 65 48 48 32 101 103 68 32 49)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 101 71 100 32 50))) (setvar (vl-list->string '(67 69 76 87 69 73 71 72 84)) 211)(command "._line" '(1.58 9.700000000000001) '(2.08 9.700000000000001) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.700000000000001) 0.04 0 (vl-list->string '(48 48 70 65 48 48 32 101 71 100 32 50)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 101 71 68 32 51))) (setvar (vl-list->string '(67 69 76 87 69 73 71 72 84)) 211)(command "._line" '(1.58 9.6) '(2.08 9.6) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.6) 0.04 0 (vl-list->string '(48 48 70 65 48 48 32 101 71 68 32 51)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 69 103 100 32 52))) (setvar (vl-list->string '(67 69 76 87 69 73 71 72 84)) 211)(command "._line" '(1.58 9.5) '(2.08 9.5) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.5) 0.04 0 (vl-list->string '(48 48 70 65 48 48 32 69 103 100 32 52)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 69 103 68 32 53))) (setvar (vl-list->string '(67 69 76 87 69 73 71 72 84)) 211)(command "._line" '(1.58 9.4) '(2.08 9.4) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.4) 0.04 0 (vl-list->string '(48 48 70 65 48 48 32 69 103 68 32 53)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 69 71 100 32 54))) (setvar (vl-list->string '(67 69 76 87 69 73 71 72 84)) 211)(command "._line" '(1.58 9.3) '(2.08 9.3) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.3) 0.04 0 (vl-list->string '(48 48 70 65 48 48 32 69 71 100 32 54)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(48 48 70 65 48 48 32 69 71 68 32 55))) (setvar (vl-list->string '(67 69 76 87 69 73 71 72 84)) 211)(command "._line" '(1.58 9.200000000000001) '(2.08 9.200000000000001) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.200000000000001) 0.04 0 (vl-list->string '(48 48 70 65 48 48 32 69 71 68 32 55)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 101 103 100 32 48))) (setvar (vl-list->string '(67 69 76 87 69 73 71 72 84)) 211)(command "._line" '(1.58 9.1) '(2.08 9.1) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.1) 0.04 0 (vl-list->string '(70 70 70 70 70 70 32 101 103 100 32 48)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 101 103 68 32 49))) (setvar (vl-list->string '(67 69 76 87 69 73 71 72 84)) 211)(command "._line" '(1.58 9.0) '(2.08 9.0) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 9.0) 0.04 0 (vl-list->string '(70 70 70 70 70 70 32 101 103 68 32 49)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 101 71 100 32 50))) (setvar (vl-list->string '(67 69 76 87 69 73 71 72 84)) 211)(command "._line" '(1.58 8.9) '(2.08 8.9) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.9) 0.04 0 (vl-list->string '(70 70 70 70 70 70 32 101 71 100 32 50)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 101 71 68 32 51))) (setvar (vl-list->string '(67 69 76 87 69 73 71 72 84)) 211)(command "._line" '(1.58 8.8) '(2.08 8.8) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.8) 0.04 0 (vl-list->string '(70 70 70 70 70 70 32 101 71 68 32 51)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 69 103 100 32 52))) (setvar (vl-list->string '(67 69 76 87 69 73 71 72 84)) 211)(command "._line" '(1.58 8.700000000000001) '(2.08 8.700000000000001) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.700000000000001) 0.04 0 (vl-list->string '(70 70 70 70 70 70 32 69 103 100 32 52)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 69 103 68 32 53))) (setvar (vl-list->string '(67 69 76 87 69 73 71 72 84)) 211)(command "._line" '(1.58 8.6) '(2.08 8.6) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.6) 0.04 0 (vl-list->string '(70 70 70 70 70 70 32 69 103 68 32 53)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 69 71 100 32 54))) (setvar (vl-list->string '(67 69 76 87 69 73 71 72 84)) 211)(command "._line" '(1.58 8.5) '(2.08 8.5) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.5) 0.04 0 (vl-list->string '(70 70 70 70 70 70 32 69 71 100 32 54)) )
(setvar (vl-list->string '(67 76 65 89 69 82)) (vl-list->string '(48))) (setvar (vl-list->string '(67 69 76 84 89 80 69)) (vl-list->string '(67 111 110 116 105 110 117 111 117 115))) (setvar (vl-list->string '(67 69 84 82 65 78 83 80 65 82 69 78 67 89)) 0) (setvar (vl-list->string '(67 69 76 84 83 67 65 76 69)) 0.9) (setvar (vl-list->string '(84 69 88 84 83 84 89 76 69)) (vl-list->string '(83 116 97 110 100 97 114 100)))(setvar (vl-list->string '(67 69 67 79 76 79 82)) (vl-list->string '(82 71 66 58 49 57 53 44 48 44 48))) (setvar (vl-list->string '(67 80 76 79 84 83 84 89 76 69)) (vl-list->string '(70 70 70 70 70 70 32 69 71 68 32 55))) (setvar (vl-list->string '(67 69 76 87 69 73 71 72 84)) 211)(command "._line" '(1.58 8.4) '(2.08 8.4) "")(setvar (vl-list->string '(67 69 67 79 76 79 82))(vl-list->string '(82 71 66 58 48 44 48 44 48))) (setvar (vl-list->string '(67 80 76 79 84 83 84 89 76 69))(vl-list->string '(78 111 114 109 97 108))) (setvar (vl-list->string '(67 69 76 87 69 73 71 72 84))0)(command "text"(vl-list->string '(74 117 115 116 105 102 121))(vl-list->string '(77 82))'(1.5 8.4) 0.04 0 (vl-list->string '(70 70 70 70 70 70 32 69 71 68 32 55)) )
